module ietf-tvr-bundle-schedule {
  yang-version 1.1;
  namespace "urn:ietf:params:xml:ns:yang:ietf-tvr-bundle-schedule";
  prefix bundle-schedule;

  import ietf-bundle-protocol {
    prefix bundle;
  }
  import ietf-tvr-schedule {
    prefix tvr-schd;
  }
  import ietf-yang-types {
    prefix yang;
  }

  organization
    "IETF TVR - Time Variant Routing Working Group";
  contact
    "WG Web:   <http://datatracker.ietf.org/wg/tvr>
     WG List:  <mailto:tvr@ietf.org>

     Author:   Marc Blanchet
               <mailto:marc.blanchet@viagenie.ca>
     Author:   Yingzhen Qu
               <mailto:yingzhen.ietf@gmail.com>
     Author:   Leigh Jordan Torgerson
               <mailto:jordan.l.torgerson@jpl.nasa.gov>";
  description
    "The YANG module defines an augmentation to the Bundle
     protocol YANG model.

     This YANG model conforms to the Network Management
     Datastore Architecture (NMDA) as described in RFC 8342.

     Copyright (c) 2024 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     This version of this YANG module is part of RFC XXXX
     (https://www.rfc-editor.org/info/rfcXXXX); see the RFC itself
     for full legal notices.

     The key words 'MUST', 'MUST NOT', 'REQUIRED', 'SHALL', 'SHALL
     NOT', 'SHOULD', 'SHOULD NOT', 'RECOMMENDED', 'NOT RECOMMENDED',
     'MAY', and 'OPTIONAL' in this document are to be interpreted as
     described in BCP 14 (RFC 2119) (RFC 8174) when, and only when,
     they appear in all capitals, as shown here.";
  reference
    "RFC XXXX: Contact Plan YANG Model for Time-Variant Routing of
               the Bundle Protocol";

  revision 2024-07-06 {
    description
      "Initial Version";
    reference
      "RFC XXXX: Contact Plan YANG Model for Time-Variant Routing
                 of the Bundle Protocol.";
  }

  augment "/bundle:node/bundle:neighbors/bundle:neighbor" {
    container contact-schedule {
      description
        "Augment Bundle node neighbor with a contact schedule.";

      uses tvr-schd:tvr-schedule {
        augment "schedules/attr-value" {
          description
            "Augment the power state within each period.";
          leaf bandwidth {
            type yang:gauge64;
            units "bits/second";
            description
              "An estimate of the convergence layer bandwidth
              in bits per second during the scheduled time.";
          }
        }
      }

      leaf bandwidth {
        type yang:gauge64;
        units "bits/second";
        default "0";
        description
          "The convergence layer default bandwidth in bits
           per second.";
      }
    }
    description
      "Augment the neighbor with a contact schedule.";
  }
}
